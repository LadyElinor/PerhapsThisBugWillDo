"""Audit explicit physical parts and export to a new directory.

Build with Build_ParametricFixtures.FCMacro first. WEEVIL_SELECTION can name
a different JSON part manifest; WEEVIL_EXPORT_DIR can name a new output folder.
"""
from datetime import datetime, timezone
import json
import os
from pathlib import Path
import sys
import FreeCAD as App

CAD = Path(__file__).resolve().parent
sys.path.insert(0, str(CAD / "scripts"))
from freecad_audit import audit_document, digest, export_verified


def main():
    doc = App.ActiveDocument
    if doc is None:
        raise RuntimeError("No active document. Build/open the parametric fixtures first.")
    selection = Path(os.environ.get("WEEVIL_SELECTION", CAD / "fixture_selection.json"))
    manifest = json.loads(selection.read_text(encoding="utf-8"))
    report, shapes = audit_document(doc, manifest)
    if not report["passed"]:
        raise RuntimeError("Export blocked: " + "; ".join(report["errors"]))
    stamp = datetime.now(timezone.utc).strftime("%Y%m%dT%H%M%S_%fZ")
    destination = Path(os.environ.get("WEEVIL_EXPORT_DIR", CAD / "exports" / "generated" / stamp))
    destination.mkdir(parents=True, exist_ok=False)
    try:
        report["export"] = export_verified(shapes, destination / "fixtures_ap242.step")
        fcstd = destination / "Fixtures.FCStd"
        doc.saveAs(str(fcstd.resolve()))
        report["fcstd_sha256"] = digest(fcstd)
        report["selection_sha256"] = digest(selection)
    except Exception as exc:
        report["passed"] = False
        report["errors"].append(str(exc))
        raise
    finally:
        (destination / "audit.json").write_text(json.dumps(report, indent=2, allow_nan=False) + "\n")
    App.Console.PrintMessage(f"Verified concept export: {destination}\n")


if __name__ == "__main__":
    main()
